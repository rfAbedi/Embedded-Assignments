# StatusClassifier_requirementSet

## #1: انتقال به وضعیت هشدار (Functional)
اگر تعداد سیگنال‌های متوالی missed بیشتر از مقدار آستانه شد، سیستم باید در وضعیت هشدار قرار بگیرد

## #2: انتقال به وضعیت عادی (Functional)
اگر تعداد سیگنال‌های متوالی ok بیشتر از مقدار آستانه شد، سیستم باید در وضعیت عادی قرار بگیرد

## #3: ریست شدن سیگنال‌های missed متوالی (Functional)
اگر سیستم در وضعیت عادی باشد، به محض دریافت یک سیگنال ok باید توالی محاسبات تعداد سیگنال‌های missed ریست شود و از صفر شمارش را آغاز کند

## #4: ریست شدن سیگنال‌های ok متوالی (Functional)
اگر سیستم در وضعیت هشدار باشد، به محض دریافت یک سیگنال misssed باید توالی محاسبات تعداد سیگنال‌های ok ریست شود و از صفر شمارش را آغاز کند

## #5: شمارش سیگنال‌های missed (Functional)
سیستم در وضعیت عادی باید تعداد سیگنال‌های missed متوالی را شمارش کند

## #6: شمارش سیگنال‌های ok (Functional)
سیستم در وضعیت هشدار باید تعداد سیگنال‌های ok متوالی را شمارش کند
