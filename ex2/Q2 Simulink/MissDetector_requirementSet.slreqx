# MissDetector_requirementSet

## #1: فعال شدن سیگنال missed (Functional)
اگر در فاصله زمانی بین کلاک اول تا دوم، سیگنال سنسور دریافت نشد، سیگنال missed ارسال شود

## #2: فعال شدن سیگنال ok (Functional)
اگر همزمان با کلاک اول یا تا قبل از کلاک دوم سیگنال سنسور دریافت شد، سیگنال ok فعال شود

## #3: انتظار کلاک دوم (Functional)
زمانی که کلاک اول دیده شد، سیستم باید در وضعیت انتظار برای دیدن کلاک دوم قرار بگیرد
